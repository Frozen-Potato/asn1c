-- OK: aligned PER keeps DEFAULT members; a root member or extension addition
-- equal to its DEFAULT is omitted

-- iso.org.dod.internet.private.enterprise (1.3.6.1.4.1)
-- .spelio.software.asn1c.test (9363.1.5.1)
-- .163

ModuleDefaultAper
	{ iso org(3) dod(6) internet(1) private(4) enterprise(1)
		spelio(9363) software(1) asn1c(5) test(1) 163 }
	DEFINITIONS AUTOMATIC TAGS ::=
BEGIN

	T ::= SEQUENCE {
		a	BOOLEAN DEFAULT TRUE,
		b	INTEGER (0..7) DEFAULT 0,
		c	INTEGER (0..7) DEFAULT 5,
		...,
		x	INTEGER (0..7) DEFAULT 1,
		y	INTEGER (0..7) DEFAULT 5
	}

	-- Extension additions with a DEFAULT: extZero (default 0) is stored by
	-- value in C, extNon (default 5) behind a pointer.
	U ::= SEQUENCE {
		a	BOOLEAN DEFAULT TRUE,
		...,
		extZero	INTEGER (0..7) DEFAULT 0,
		extNon	INTEGER (0..7) DEFAULT 5
	}

	-- BMPString / UniversalString DEFAULT: stored as UCS-2 / UCS-4 big-endian
	V ::= SEQUENCE {
		a	BMPString DEFAULT "hi",
		u	UniversalString DEFAULT "hi",
		b	BOOLEAN
	}

	-- UTF8String and UTCTime DEFAULT: the literal's bytes as written
	W ::= SEQUENCE {
		a	UTF8String DEFAULT "é€",
		t	UTCTime DEFAULT "250102030405Z",
		b	BOOLEAN
	}

	-- NULL DEFAULT: a present NULL is always the default, so it is omitted
	X ::= SEQUENCE {
		n	NULL DEFAULT NULL,
		b	BOOLEAN
	}

	-- REAL DEFAULT: decimal, integer form, signed, the three special
	-- values and minus zero
	Y ::= SEQUENCE {
		r	REAL DEFAULT 1.5,
		z	REAL DEFAULT 0,
		m	REAL DEFAULT -2.25,
		p	REAL DEFAULT PLUS-INFINITY,
		q	REAL DEFAULT MINUS-INFINITY,
		na	REAL DEFAULT NOT-A-NUMBER,
		nz	REAL DEFAULT -0.0,
		b	BOOLEAN
	}

END
