-- OK: OCTET STRING / BIT STRING DEFAULT given as hstring or bstring

-- iso.org.dod.internet.private.enterprise (1.3.6.1.4.1)
-- .spelio.software.asn1c.test (9363.1.5.1)
-- .162

ModuleDefaultBlob
	{ iso org(3) dod(6) internet(1) private(4) enterprise(1)
		spelio(9363) software(1) asn1c(5) test(1) 162 }
	DEFINITIONS AUTOMATIC TAGS ::=
BEGIN

	T ::= SEQUENCE {
		o	OCTET STRING DEFAULT 'AB'H,
		b	BIT STRING DEFAULT '101'B,
		w	BIT STRING DEFAULT 'A5'H,
		n	BIT STRING {x(0), y(1)} DEFAULT {x}
	}

END
