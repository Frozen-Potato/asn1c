-- OK: DEFAULT of a named-bit BIT STRING ({ names }, { }, hstring) and of
-- OBJECT IDENTIFIER / RELATIVE-OID ({ arcs }, { name(arc) arc }); a named-bit
-- value that differs from the DEFAULT only in trailing 0 bits is equal to it;
-- the DEFAULT of an OBJECT IDENTIFIER / RELATIVE-OID given by value references
-- (a whole reference, { value arc }, { value rel-value }, name(integer-value),
-- a value imported from another module)

-- iso.org.dod.internet.private.enterprise (1.3.6.1.4.1)
-- .spelio.software.asn1c.test (9363.1.5.1)
-- .173

ModuleDefaultNamedBitOid
	{ iso org(3) dod(6) internet(1) private(4) enterprise(1)
		spelio(9363) software(1) asn1c(5) test(1) 173 }
	DEFINITIONS AUTOMATIC TAGS ::=
BEGIN

	IMPORTS id-ext FROM ModuleDefaultOidBase;

	id-base OBJECT IDENTIFIER ::= { 1 3 6 1 }
	id-alias OBJECT IDENTIFIER ::= id-base
	id-pen OBJECT IDENTIFIER ::= { id-base 4 1 }
	rel-x RELATIVE-OID ::= { 8 9 }
	arc-n INTEGER ::= 42

	Flags8 ::= BIT STRING { p(0), q(1), r(9) } (SIZE (8..16))
	Fixed8 ::= BIT STRING { app(0), enrol(1) } (SIZE (8))
	OidNamed ::= OBJECT IDENTIFIER

	T ::= SEQUENCE {
		a	BIT STRING { p(0), q(1), r(2) } DEFAULT { p, r },
		e	BIT STRING { p(0), q(1) } DEFAULT { },
		h	BIT STRING { p(0), q(1), r(2) } DEFAULT '60'H,
		f	Flags8 DEFAULT { q },
		x	Fixed8 DEFAULT { app },
		o	OBJECT IDENTIFIER DEFAULT { 1 3 6 1 4 1 9363 },
		n	OidNamed DEFAULT { iso(1) org(3) 6 },
		r	RELATIVE-OID DEFAULT { 1 2 300 },
		b	BOOLEAN
	}

	U ::= SEQUENCE {
		a	OBJECT IDENTIFIER DEFAULT id-base,
		b	OBJECT IDENTIFIER DEFAULT { id-base 5 },
		c	OBJECT IDENTIFIER DEFAULT id-pen,
		d	OBJECT IDENTIFIER DEFAULT id-alias,
		e	OBJECT IDENTIFIER DEFAULT { id-ext 15 },
		f	OBJECT IDENTIFIER DEFAULT { id-base rel-x },
		g	OBJECT IDENTIFIER DEFAULT { id-base n(arc-n) },
		i	RELATIVE-OID DEFAULT { rel-x 1 },
		z	BOOLEAN
	}

END

ModuleDefaultOidBase DEFINITIONS AUTOMATIC TAGS ::=
BEGIN
	EXPORTS ALL;
	id-ext OBJECT IDENTIFIER ::= { 2 5 29 }
END
