PhcVec DEFINITIONS AUTOMATIC TAGS ::= BEGIN
SoInt ::= SET (SIZE(0..4)) OF INTEGER (0..255)
SoOcts ::= SET OF OCTET STRING
SoSeq ::= SET (SIZE(1..8)) OF SEQUENCE { f BOOLEAN, o OCTET STRING (SIZE(0..4)) }
END
