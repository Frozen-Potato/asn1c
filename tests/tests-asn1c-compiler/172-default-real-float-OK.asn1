-- OK: a REAL DEFAULT on a float-narrowed type (X.696 12.2: the member is a C
-- float); the default is stored rounded to float, and a float equal to it is
-- omitted

-- iso.org.dod.internet.private.enterprise (1.3.6.1.4.1)
-- .spelio.software.asn1c.test (9363.1.5.1)
-- .172

ModuleDefaultRealFloat
	{ iso org(3) dod(6) internet(1) private(4) enterprise(1)
		spelio(9363) software(1) asn1c(5) test(1) 172 }
	DEFINITIONS AUTOMATIC TAGS ::=
BEGIN

	Z ::= SEQUENCE {
		f	REAL (WITH COMPONENTS { mantissa (-16777215..16777215),
				base (2), exponent (-100..100) }) DEFAULT 0.1,
		g	REAL (WITH COMPONENTS { mantissa (-16777215..16777215),
				base (2), exponent (-100..100) }) DEFAULT PLUS-INFINITY,
		b	BOOLEAN
	}

END
