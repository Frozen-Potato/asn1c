-- OK: PER "normally small" values >= 64: extension-addition bitmap length
-- (X.691 11.9.3.4), CHOICE extension index and ENUMERATED extension value
-- (X.691 11.6)

-- iso.org.dod.internet.private.enterprise (1.3.6.1.4.1)
-- .spelio.software.asn1c.test (9363.1.5.1)
-- .164

ModuleNSmall64
	{ iso org(3) dod(6) internet(1) private(4) enterprise(1)
		spelio(9363) software(1) asn1c(5) test(1) 164 }
	DEFINITIONS AUTOMATIC TAGS ::=
BEGIN

	Seq70 ::= SEQUENCE {
		r	BOOLEAN,
		...,
		e0	BOOLEAN OPTIONAL,
		e1	BOOLEAN OPTIONAL,
		e2	BOOLEAN OPTIONAL,
		e3	BOOLEAN OPTIONAL,
		e4	BOOLEAN OPTIONAL,
		e5	BOOLEAN OPTIONAL,
		e6	BOOLEAN OPTIONAL,
		e7	BOOLEAN OPTIONAL,
		e8	BOOLEAN OPTIONAL,
		e9	BOOLEAN OPTIONAL,
		e10	BOOLEAN OPTIONAL,
		e11	BOOLEAN OPTIONAL,
		e12	BOOLEAN OPTIONAL,
		e13	BOOLEAN OPTIONAL,
		e14	BOOLEAN OPTIONAL,
		e15	BOOLEAN OPTIONAL,
		e16	BOOLEAN OPTIONAL,
		e17	BOOLEAN OPTIONAL,
		e18	BOOLEAN OPTIONAL,
		e19	BOOLEAN OPTIONAL,
		e20	BOOLEAN OPTIONAL,
		e21	BOOLEAN OPTIONAL,
		e22	BOOLEAN OPTIONAL,
		e23	BOOLEAN OPTIONAL,
		e24	BOOLEAN OPTIONAL,
		e25	BOOLEAN OPTIONAL,
		e26	BOOLEAN OPTIONAL,
		e27	BOOLEAN OPTIONAL,
		e28	BOOLEAN OPTIONAL,
		e29	BOOLEAN OPTIONAL,
		e30	BOOLEAN OPTIONAL,
		e31	BOOLEAN OPTIONAL,
		e32	BOOLEAN OPTIONAL,
		e33	BOOLEAN OPTIONAL,
		e34	BOOLEAN OPTIONAL,
		e35	BOOLEAN OPTIONAL,
		e36	BOOLEAN OPTIONAL,
		e37	BOOLEAN OPTIONAL,
		e38	BOOLEAN OPTIONAL,
		e39	BOOLEAN OPTIONAL,
		e40	BOOLEAN OPTIONAL,
		e41	BOOLEAN OPTIONAL,
		e42	BOOLEAN OPTIONAL,
		e43	BOOLEAN OPTIONAL,
		e44	BOOLEAN OPTIONAL,
		e45	BOOLEAN OPTIONAL,
		e46	BOOLEAN OPTIONAL,
		e47	BOOLEAN OPTIONAL,
		e48	BOOLEAN OPTIONAL,
		e49	BOOLEAN OPTIONAL,
		e50	BOOLEAN OPTIONAL,
		e51	BOOLEAN OPTIONAL,
		e52	BOOLEAN OPTIONAL,
		e53	BOOLEAN OPTIONAL,
		e54	BOOLEAN OPTIONAL,
		e55	BOOLEAN OPTIONAL,
		e56	BOOLEAN OPTIONAL,
		e57	BOOLEAN OPTIONAL,
		e58	BOOLEAN OPTIONAL,
		e59	BOOLEAN OPTIONAL,
		e60	BOOLEAN OPTIONAL,
		e61	BOOLEAN OPTIONAL,
		e62	BOOLEAN OPTIONAL,
		e63	BOOLEAN OPTIONAL,
		e64	BOOLEAN OPTIONAL,
		e65	BOOLEAN OPTIONAL,
		e66	BOOLEAN OPTIONAL,
		e67	BOOLEAN OPTIONAL,
		e68	BOOLEAN OPTIONAL,
		e69	BOOLEAN OPTIONAL
	}

	Ch70 ::= CHOICE {
		r	BOOLEAN,
		...,
		c0	BOOLEAN,
		c1	BOOLEAN,
		c2	BOOLEAN,
		c3	BOOLEAN,
		c4	BOOLEAN,
		c5	BOOLEAN,
		c6	BOOLEAN,
		c7	BOOLEAN,
		c8	BOOLEAN,
		c9	BOOLEAN,
		c10	BOOLEAN,
		c11	BOOLEAN,
		c12	BOOLEAN,
		c13	BOOLEAN,
		c14	BOOLEAN,
		c15	BOOLEAN,
		c16	BOOLEAN,
		c17	BOOLEAN,
		c18	BOOLEAN,
		c19	BOOLEAN,
		c20	BOOLEAN,
		c21	BOOLEAN,
		c22	BOOLEAN,
		c23	BOOLEAN,
		c24	BOOLEAN,
		c25	BOOLEAN,
		c26	BOOLEAN,
		c27	BOOLEAN,
		c28	BOOLEAN,
		c29	BOOLEAN,
		c30	BOOLEAN,
		c31	BOOLEAN,
		c32	BOOLEAN,
		c33	BOOLEAN,
		c34	BOOLEAN,
		c35	BOOLEAN,
		c36	BOOLEAN,
		c37	BOOLEAN,
		c38	BOOLEAN,
		c39	BOOLEAN,
		c40	BOOLEAN,
		c41	BOOLEAN,
		c42	BOOLEAN,
		c43	BOOLEAN,
		c44	BOOLEAN,
		c45	BOOLEAN,
		c46	BOOLEAN,
		c47	BOOLEAN,
		c48	BOOLEAN,
		c49	BOOLEAN,
		c50	BOOLEAN,
		c51	BOOLEAN,
		c52	BOOLEAN,
		c53	BOOLEAN,
		c54	BOOLEAN,
		c55	BOOLEAN,
		c56	BOOLEAN,
		c57	BOOLEAN,
		c58	BOOLEAN,
		c59	BOOLEAN,
		c60	BOOLEAN,
		c61	BOOLEAN,
		c62	BOOLEAN,
		c63	BOOLEAN,
		c64	BOOLEAN,
		c65	BOOLEAN,
		c66	BOOLEAN,
		c67	BOOLEAN,
		c68	BOOLEAN,
		c69	BOOLEAN
	}

	En70 ::= ENUMERATED {
		r(0),
		...,
		v0(1),
		v1(2),
		v2(3),
		v3(4),
		v4(5),
		v5(6),
		v6(7),
		v7(8),
		v8(9),
		v9(10),
		v10(11),
		v11(12),
		v12(13),
		v13(14),
		v14(15),
		v15(16),
		v16(17),
		v17(18),
		v18(19),
		v19(20),
		v20(21),
		v21(22),
		v22(23),
		v23(24),
		v24(25),
		v25(26),
		v26(27),
		v27(28),
		v28(29),
		v29(30),
		v30(31),
		v31(32),
		v32(33),
		v33(34),
		v34(35),
		v35(36),
		v36(37),
		v37(38),
		v38(39),
		v39(40),
		v40(41),
		v41(42),
		v42(43),
		v43(44),
		v44(45),
		v45(46),
		v46(47),
		v47(48),
		v48(49),
		v49(50),
		v50(51),
		v51(52),
		v52(53),
		v53(54),
		v54(55),
		v55(56),
		v56(57),
		v57(58),
		v58(59),
		v59(60),
		v60(61),
		v61(62),
		v62(63),
		v63(64),
		v64(65),
		v65(66),
		v66(67),
		v67(68),
		v68(69),
		v69(70)
	}

END
