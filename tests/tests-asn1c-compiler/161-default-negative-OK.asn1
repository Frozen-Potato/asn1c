-- OK: Negative and boundary INTEGER DEFAULT values yield valid C names
-- Also see .134 for 64-bit integers.

-- iso.org.dod.internet.private.enterprise (1.3.6.1.4.1)
-- .spelio.software.asn1c.test (9363.1.5.1)
-- .161

ModuleDefaultNegative
	{ iso org(3) dod(6) internet(1) private(4) enterprise(1)
		spelio(9363) software(1) asn1c(5) test(1) 161 }
	DEFINITIONS AUTOMATIC TAGS ::=
BEGIN

	T ::= SEQUENCE {
		neg	INTEGER (-10..10) DEFAULT -1,
		min64	INTEGER (-9223372036854775808..9223372036854775807) DEFAULT -9223372036854775808,
		pos	INTEGER (-10..10) DEFAULT 5
	}

END
