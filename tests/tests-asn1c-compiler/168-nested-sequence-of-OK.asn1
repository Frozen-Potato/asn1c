-- OK: nested and wide-INTEGER SEQUENCE OF / SET OF
--   SEQUENCE OF / SET OF an inline unsigned INTEGER whose range needs its own
--   type descriptor (INTEGER (0..4294967295)) as the element; SEQUENCE OF / SET OF
--   nested two or three levels with an inline SEQUENCE / CHOICE innermost;
--   SIZE constraints on both the outer and the inner list.

-- iso.org.dod.internet.private.enterprise (1.3.6.1.4.1)
-- .spelio.software.asn1c.test (9363.1.5.1)
-- .168

ModuleNestedSequenceOf
	{ iso org(3) dod(6) internet(1) private(4) enterprise(1)
		spelio(9363) software(1) asn1c(5) test(1) 168 }
	DEFINITIONS AUTOMATIC TAGS ::=
BEGIN

	-- An inline unsigned INTEGER element that has its own type descriptor.
	WideTop ::= SEQUENCE OF INTEGER (0..4294967295)
	WideTopSet ::= SET OF INTEGER (0..4294967295)
	WideMember ::= SEQUENCE {
		l SEQUENCE (SIZE(1..4)) OF INTEGER (0..4294967295),
		s SET (SIZE(1..4)) OF INTEGER (1..4294967295) OPTIONAL
	}

	-- A SEQUENCE / CHOICE inside two nested lists.
	NestSeq ::= SEQUENCE OF SEQUENCE OF SEQUENCE { a BOOLEAN }
	NestSet ::= SET OF SET OF SEQUENCE { a BOOLEAN }
	NestChoice ::= SEQUENCE OF SEQUENCE OF CHOICE { a BOOLEAN, b INTEGER (0..7) }
	NestChoiceSet ::= SET OF SET OF CHOICE { a BOOLEAN, b INTEGER (0..7) }
	NestWide ::= SEQUENCE OF SEQUENCE OF INTEGER (0..4294967295)
	Deep ::= SEQUENCE OF SEQUENCE {
		x SEQUENCE OF SEQUENCE OF SEQUENCE { a BOOLEAN }
	}

	-- SIZE on both the outer and the inner list.
	Sized ::= SEQUENCE (SIZE(1..4)) OF SEQUENCE (SIZE(1..4)) OF SEQUENCE { a BOOLEAN }
	SizedSet ::= SET (SIZE(1..4)) OF SET (SIZE(2..3)) OF SEQUENCE { a BOOLEAN }
	SizedWide ::= SEQUENCE (SIZE(1..2)) OF SET (SIZE(1..3)) OF INTEGER (0..4294967295)
	SizedMember ::= SEQUENCE {
		m SEQUENCE (SIZE(1..4)) OF SEQUENCE (SIZE(2..3)) OF INTEGER (0..7)
	}

END
