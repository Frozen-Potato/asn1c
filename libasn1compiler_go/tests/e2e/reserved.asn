Reserved DEFINITIONS AUTOMATIC TAGS ::= BEGIN

-- Names that are C reserved words, as CHOICE alternatives, SEQUENCE members
-- and enumerators. asn1c upper-cases the first letter of a reserved-word
-- struct/union member (Explicit) but keeps the lower-case _PR constant.

RsH ::= SEQUENCE { explicit BOOLEAN, int INTEGER (0..3) OPTIONAL }

RsC ::= CHOICE { explicit BOOLEAN, x NULL }

RsE ::= ENUMERATED { explicit, auto }

RsR ::= CHOICE {
	explicit	BOOLEAN,
	int		INTEGER (0..7),
	auto		OCTET STRING (SIZE(2)),
	default		SEQUENCE { a INTEGER (0..3) },
	struct		CHOICE { p BOOLEAN, q INTEGER (0..3) },
	x		NULL,
	static		NULL
}

END
