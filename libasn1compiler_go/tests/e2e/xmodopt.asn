XoA DEFINITIONS AUTOMATIC TAGS ::= BEGIN

-- Two shapes of an OPTIONAL member of an imported type, imported by a module
-- that declares no BIT STRING of its own: an OPTIONAL member whose type is a
-- named BIT STRING, and an OPTIONAL inline SEQUENCE OF.
XoRnti ::= BIT STRING (SIZE(16))
XoIt ::= SEQUENCE { n INTEGER (0..7) }
XoBits ::= SEQUENCE { r XoRnti OPTIONAL, k INTEGER (0..7) }
XoList ::= SEQUENCE { l SEQUENCE (SIZE(1..4)) OF XoIt OPTIONAL, k INTEGER (0..7) }

END

XoB DEFINITIONS AUTOMATIC TAGS ::= BEGIN

IMPORTS XoBits, XoList FROM XoA;

XoMsg ::= SEQUENCE { b XoBits, l XoList }

END
