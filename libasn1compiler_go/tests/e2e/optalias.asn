OptAlias DEFINITIONS AUTOMATIC TAGS ::= BEGIN

-- An alias of an alias used as an OPTIONAL SEQUENCE member and as a CHOICE
-- alternative (with -findirect-choice both are "struct" pointers).

Freq ::= SEQUENCE { f INTEGER (0..16383) }
PFL ::= Freq
M ::= SEQUENCE { a INTEGER (0..3), pf PFL OPTIONAL }
C ::= CHOICE { a INTEGER (0..3), pf PFL }

END
