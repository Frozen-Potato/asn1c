PadAlloc DEFINITIONS AUTOMATIC TAGS ::=
BEGIN

-- Types whose C Flat struct (or SEQUENCE OF element) is NOT a multiple of 8
-- bytes, held behind a pointer or in an item array and followed by further
-- fixed-region allocations. The Go size pass must reserve exactly what the
-- 8-aligned arena allocator consumes ("fixed-region undercounted by 4").
-- Shape: a CHOICE inside a CHOICE inside a list item, the innermost alt a
-- 4-byte struct. Driven by randenc_test.go.

	-- a 4-byte Flat struct
	Mimo ::= SEQUENCE {
		state	ENUMERATED { a, b, c },
		...
	}

	PaOther ::= SEQUENCE {
		x	INTEGER (0..7),
		y	OCTET STRING (SIZE(1..3)) OPTIONAL
	}

	-- the nested shape: a 4-byte struct is a CHOICE alt (a pointer under
	-- -findirect-choice) inside an alt, inside a list item that carries
	-- further OPTIONAL allocations
	PaInner ::= CHOICE {
		mimo	Mimo,
		other	PaOther,
		...
	}

	PaOuter ::= CHOICE {
		inner	PaInner,
		flag	BOOLEAN,
		...
	}

	PaItem ::= SEQUENCE {
		id		INTEGER (0..3),
		trigger		PaOuter,
		logicalOr	ENUMERATED { true, ... } OPTIONAL
	}

	ItemList ::= SEQUENCE (SIZE(1..3)) OF PaItem

	-- a 4-byte struct behind an OPTIONAL pointer, then more allocations
	OptMimo ::= SEQUENCE {
		m	Mimo OPTIONAL,
		s	OCTET STRING (SIZE(1..4)) OPTIONAL,
		n	INTEGER (0..3) OPTIONAL,
		m2	Mimo OPTIONAL,
		b	BOOLEAN OPTIONAL
	}

	-- SEQUENCE OF with a 4-byte element stride (an odd-length array ends
	-- mid-word), followed by more allocations
	EnumList ::= SEQUENCE (SIZE(1..3)) OF ENUMERATED { a, b, c }
	MimoList ::= SEQUENCE (SIZE(1..3)) OF Mimo

	Lists ::= SEQUENCE {
		l1	EnumList,
		l2	MimoList,
		l3	EnumList OPTIONAL,
		tail	OCTET STRING (SIZE(1..2)) OPTIONAL,
		l4	MimoList OPTIONAL,
		n	INTEGER (0..3) OPTIONAL
	}

	-- list items that are themselves 4-byte structs behind a CHOICE alt
	MimoAlts ::= SEQUENCE (SIZE(1..3)) OF CHOICE {
		mimo	Mimo,
		n	INTEGER (0..3),
		s	OCTET STRING (SIZE(1..2))
	}

END
