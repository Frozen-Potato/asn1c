Defaults DEFINITIONS AUTOMATIC TAGS ::=
BEGIN

IMPORTS id-ext FROM DefaultsOidBase;

-- DEFAULT members: a plain value in Go, the C runtime decides omission.

Colour ::= ENUMERATED { red, green, blue, ... }

Inner ::= SEQUENCE {
    x   BOOLEAN DEFAULT FALSE,
    y   INTEGER (0..255) DEFAULT 200,
    ...
}

DefaultsPDU ::= SEQUENCE {
    flag    BOOLEAN DEFAULT TRUE,
    small   INTEGER (0..7) DEFAULT 0,
    signed  INTEGER (-10..10) DEFAULT -1,
    min32   INTEGER (-2147483648..0) DEFAULT -2147483648,
    min64   INTEGER DEFAULT -9223372036854775808,
    colour  Colour DEFAULT green,
    inl     ENUMERATED { a, b, c } DEFAULT b,
    name    PrintableString DEFAULT "hi",
    octs    OCTET STRING DEFAULT 'AB'H,
    bits    BIT STRING DEFAULT '101'B,
    inner   Inner,
    ...
}

-- DEFAULT members as extension additions: one with default 0 (stored by value
-- in C) and one with a non-zero default (stored behind a pointer).
ExtDefaults ::= SEQUENCE {
    a       BOOLEAN DEFAULT TRUE,
    ...,
    extZero INTEGER (0..7) DEFAULT 0,
    extNon  INTEGER (0..7) DEFAULT 5
}

-- INTEGER_t storage (the range does not fit a C long): the C slot is a
-- pointer to INTEGER_t even for the default 0.
Big ::= INTEGER (0..1099511627775)

WideDefaults ::= SEQUENCE {
    w5  Big DEFAULT 5,
    w0  Big DEFAULT 0,
    ...
}

-- NULL and REAL DEFAULT: a present NULL always equals its DEFAULT; a REAL
-- compares exactly (NaN equals NaN, -0.0 is not 0.0).
RealDefaults ::= SEQUENCE {
    n   NULL DEFAULT NULL,
    r   REAL DEFAULT 1.5,
    z   REAL DEFAULT 0,
    m   REAL DEFAULT -2.25,
    p   REAL DEFAULT PLUS-INFINITY,
    q   REAL DEFAULT MINUS-INFINITY,
    nz  REAL DEFAULT -0.0,
    na  REAL DEFAULT NOT-A-NUMBER,
    b   BOOLEAN
}

-- Named-bit BIT STRING DEFAULT ({ names }, { }), plain and under SIZE
-- constraints (a fixed size and a range): the value is held without trailing
-- 0 bits, padded to the lower bound of the SIZE constraint.
Perms ::= BIT STRING { read(0), write(1), exec(2) }
FixedPerms ::= BIT STRING { read(0), write(1) } (SIZE (4))
RangePerms ::= BIT STRING { read(0), write(1) } (SIZE (2..6))

BitDefaults ::= SEQUENCE {
    a   BIT STRING { p(0), q(1), r(2) } DEFAULT { p, r },
    e   BIT STRING { p(0), q(1) } DEFAULT { },
    f   FixedPerms DEFAULT { write },
    g   RangePerms DEFAULT { read },
    h   Perms DEFAULT { },
    b   BOOLEAN
}

-- OBJECT IDENTIFIER and RELATIVE-OID DEFAULT, with number and name(number) arcs.
OidDefaults ::= SEQUENCE {
    o   OBJECT IDENTIFIER DEFAULT { 1 3 6 1 4 1 9363 },
    n   OBJECT IDENTIFIER DEFAULT { iso(1) org(3) 7 },
    r   RELATIVE-OID DEFAULT { 1 2 300 },
    b   BOOLEAN
}

-- OBJECT IDENTIFIER and RELATIVE-OID DEFAULT given by value references,
-- including a value imported from another module.
id-base OBJECT IDENTIFIER ::= { 1 3 6 1 }
id-alias OBJECT IDENTIFIER ::= id-base
id-pen OBJECT IDENTIFIER ::= { id-base 4 1 }
rel-x RELATIVE-OID ::= { 8 9 }
arc-n INTEGER ::= 42

OidRefDefaults ::= SEQUENCE {
    a   OBJECT IDENTIFIER DEFAULT id-base,
    b   OBJECT IDENTIFIER DEFAULT { id-base 5 },
    c   OBJECT IDENTIFIER DEFAULT id-pen,
    d   OBJECT IDENTIFIER DEFAULT id-alias,
    e   OBJECT IDENTIFIER DEFAULT { id-ext 15 },
    f   OBJECT IDENTIFIER DEFAULT { id-base rel-x },
    g   OBJECT IDENTIFIER DEFAULT { id-base n(arc-n) },
    i   RELATIVE-OID DEFAULT { rel-x 1 },
    z   BOOLEAN
}

END

DefaultsOidBase DEFINITIONS AUTOMATIC TAGS ::=
BEGIN
EXPORTS ALL;
id-ext OBJECT IDENTIFIER ::= { 2 5 29 }
END
