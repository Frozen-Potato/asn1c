NamedBit DEFINITIONS AUTOMATIC TAGS ::=
BEGIN

-- Named-bit BIT STRING: the Go value type is the plain BitString; the names
-- only become int bit-position constants. Mirrors C check-167.

	-- Bit numbers neither contiguous nor sorted.
	Caps ::= BIT STRING { c(7), a(0), b(3) }

	Fixed ::= BIT STRING { lo(0), hi(5) } (SIZE(8))
	Ranged ::= BIT STRING { p(0), q(2) } (SIZE(4..12))
	Open ::= BIT STRING { p(0), q(2) } (SIZE(4..12, ...))

	Holder ::= SEQUENCE {
		opt	BIT STRING { x(1), y(4) } (SIZE(3..6)) OPTIONAL,
		req	BIT STRING { u(0), v(2) } (SIZE(3..6)),
		flag	BOOLEAN
	}

	Item ::= BIT STRING { m(1), n(2) }

	Selector ::= CHOICE {
		flags	BIT STRING { on(0), off(1) },
		plain	BIT STRING (SIZE(2)),
		named	Item
	}

	List ::= SEQUENCE OF Item

END
