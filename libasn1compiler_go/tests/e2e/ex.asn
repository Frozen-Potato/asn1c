Synth-Example DEFINITIONS AUTOMATIC TAGS ::=
BEGIN
Example-PDU ::= SEQUENCE {
    requestId INTEGER (0..65535),
    payload   Example-Payload,
    note      PrintableString (SIZE(1..32)) OPTIONAL,
    ...
}
Example-Payload ::= CHOICE {
    text   PrintableString (SIZE(1..32)),
    number INTEGER (0..255),
    ...
}
Flag ::= BOOLEAN
Flag-PDU ::= SEQUENCE {
    enabled Flag,
    maybe   Flag OPTIONAL,
    flags   SEQUENCE (SIZE(0..4)) OF Flag,
    sel     Flag-Choice
}
Flag-Choice ::= CHOICE {
    flag Flag,
    num  INTEGER (0..7),
    ...
}
-- Regression: extensible CHOICE with two extension alternatives; the
-- extension index is a X.691 #10.6 normally small number (not range-bits).
Ext-Choice ::= CHOICE {
    base INTEGER (0..7),
    ...,
    extNum  INTEGER (0..255),
    extFlag BOOLEAN
}
END
