SeqofInl DEFINITIONS AUTOMATIC TAGS ::=
BEGIN

-- SEQUENCE OF with an inline (anonymous) element type: at top level, as a
-- SEQUENCE member, as an OPTIONAL member and as a CHOICE alternative. The C
-- backend names the element "Member"; Go gets the unnamed leaf mapping
-- ([]int64, []bool, ...) or <Owner>Member for an inline constructed element.

	-- ---- primitive elements, top level ----
	IntTop ::= SEQUENCE (SIZE(0..4)) OF INTEGER (0..3)
	WideTop ::= SEQUENCE (SIZE(0..4)) OF INTEGER (-1000000000..1000000000)
	FreeTop ::= SEQUENCE (SIZE(0..4)) OF INTEGER
	BoolTop ::= SEQUENCE (SIZE(0..4)) OF BOOLEAN
	OctTop ::= SEQUENCE (SIZE(0..4)) OF OCTET STRING (SIZE(1..3))
	BitTop ::= SEQUENCE (SIZE(0..4)) OF BIT STRING (SIZE(1..8))
	StrTop ::= SEQUENCE (SIZE(0..4)) OF PrintableString (SIZE(1..4))
	RealTop ::= SEQUENCE (SIZE(0..4)) OF REAL
	NullTop ::= SEQUENCE (SIZE(0..4)) OF NULL

	-- ---- primitive elements, member / OPTIONAL member / CHOICE alt ----
	InlHolder ::= SEQUENCE {
		a	SEQUENCE (SIZE(0..4)) OF INTEGER (0..3),
		b	SEQUENCE (SIZE(0..4)) OF BOOLEAN OPTIONAL,
		c	SEQUENCE (SIZE(0..4)) OF OCTET STRING (SIZE(1..3)) OPTIONAL,
		d	SEQUENCE (SIZE(0..4)) OF NULL OPTIONAL,
		flag	BOOLEAN
	}

	InlAlt ::= CHOICE {
		a	SEQUENCE (SIZE(0..4)) OF INTEGER (0..3),
		b	SEQUENCE (SIZE(0..4)) OF PrintableString (SIZE(1..4)),
		c	BOOLEAN
	}

	-- ---- constructed elements, top level ----
	SeqTop ::= SEQUENCE (SIZE(0..4)) OF SEQUENCE {
		x	INTEGER (0..3),
		y	BOOLEAN OPTIONAL
	}
	ChoiceTop ::= SEQUENCE (SIZE(0..4)) OF CHOICE {
		x	INTEGER (0..3),
		y	BOOLEAN
	}
	EnumTop ::= SEQUENCE (SIZE(0..4)) OF ENUMERATED { red, green, blue }
	NestTop ::= SEQUENCE (SIZE(0..3)) OF SEQUENCE OF INTEGER
	Nest3Top ::= SEQUENCE (SIZE(0..2)) OF SEQUENCE OF BOOLEAN
	BitsNamedTop ::= SEQUENCE (SIZE(0..4)) OF BIT STRING { p(0), q(1), r(2) }

	-- ---- constructed elements, member / OPTIONAL member / CHOICE alt ----
	SeqMem ::= SEQUENCE {
		a	SEQUENCE (SIZE(0..4)) OF SEQUENCE { x INTEGER (0..3), y BOOLEAN },
		b	SEQUENCE (SIZE(0..4)) OF CHOICE { x INTEGER (0..3), y BOOLEAN } OPTIONAL,
		c	SEQUENCE (SIZE(0..4)) OF ENUMERATED { red, green } OPTIONAL,
		d	SEQUENCE (SIZE(0..4)) OF BIT STRING { p(0), q(1) } OPTIONAL,
		flag	BOOLEAN
	}

	InlAltC ::= CHOICE {
		a	SEQUENCE (SIZE(0..4)) OF SEQUENCE { x INTEGER (0..3) },
		b	SEQUENCE (SIZE(0..4)) OF ENUMERATED { red, green },
		c	SEQUENCE (SIZE(0..4)) OF SEQUENCE OF BOOLEAN,
		d	BOOLEAN
	}

END

SofNull DEFINITIONS AUTOMATIC TAGS ::=
BEGIN

-- SEQUENCE OF a named NULL type (directly and through an alias): top level,
-- as a SEQUENCE member, as an OPTIONAL member and as a CHOICE alternative.
-- Also a plain member / alternative of the NULL type itself.

	SnN ::= NULL
	SnN2 ::= SnN

	SnTop ::= SEQUENCE (SIZE(0..4)) OF SnN
	SnAlias ::= SEQUENCE (SIZE(0..4)) OF SnN2

	SnMem ::= SEQUENCE {
		a	SEQUENCE (SIZE(0..4)) OF SnN,
		b	SEQUENCE (SIZE(0..4)) OF SnN2 OPTIONAL,
		flag	BOOLEAN
	}

	SnAlt ::= CHOICE {
		a	SEQUENCE (SIZE(0..4)) OF SnN,
		b	SnN,
		c	BOOLEAN
	}

	SnPlain ::= SEQUENCE {
		n	SnN,
		o	SnN OPTIONAL,
		flag	BOOLEAN
	}

END

OptAlias DEFINITIONS AUTOMATIC TAGS ::= BEGIN

-- An alias of an alias used as an OPTIONAL SEQUENCE member and as a CHOICE
-- alternative (with -findirect-choice both are "struct" pointers).

Freq ::= SEQUENCE { f INTEGER (0..16383) }
PFL ::= Freq
M ::= SEQUENCE { a INTEGER (0..3), pf PFL OPTIONAL }
C ::= CHOICE { a INTEGER (0..3), pf PFL }

END
