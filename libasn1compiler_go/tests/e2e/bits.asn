NamedBit DEFINITIONS AUTOMATIC TAGS ::=
BEGIN

-- Named-bit BIT STRING: the Go value type is the plain BitString; the names
-- only become int bit-position constants. Mirrors C check-167.

	-- Bit numbers neither contiguous nor sorted.
	Caps ::= BIT STRING { c(7), a(0), b(3) }

	Fixed ::= BIT STRING { lo(0), hi(5) } (SIZE(8))
	Ranged ::= BIT STRING { p(0), q(2) } (SIZE(4..12))
	Open ::= BIT STRING { p(0), q(2) } (SIZE(4..12, ...))

	Holder ::= SEQUENCE {
		opt	BIT STRING { x(1), y(4) } (SIZE(3..6)) OPTIONAL,
		req	BIT STRING { u(0), v(2) } (SIZE(3..6)),
		flag	BOOLEAN
	}

	Item ::= BIT STRING { m(1), n(2) }

	Selector ::= CHOICE {
		flags	BIT STRING { on(0), off(1) },
		plain	BIT STRING (SIZE(2)),
		named	Item
	}

	List ::= SEQUENCE OF Item

END

BitsA DEFINITIONS AUTOMATIC TAGS ::=
BEGIN

-- BIT STRING members in several modules of one -Fgo run (each module owns its
-- BitString helper type), OPTIONAL inline BIT STRINGs (C: BIT_STRING_t *) and
-- OPTIONAL references to BIT STRING types, local and imported.

	OptFixed ::= SEQUENCE {
		opt	BIT STRING (SIZE(8)) OPTIONAL,
		flag	BOOLEAN
	}

	OptVar ::= SEQUENCE {
		opt	BIT STRING (SIZE(1..160, ...)) OPTIONAL,
		flag	BOOLEAN
	}

	-- a variable-size BIT STRING plus an optional fixed-size one
	TnlInfo ::= SEQUENCE {
		tnlAddress	BIT STRING (SIZE(1..160, ...)),
		tnlPort	BIT STRING (SIZE(16)) OPTIONAL,
		...
	}

	RangedBits ::= BIT STRING (SIZE(4..12))
	CapsBits ::= BIT STRING { c(7), a(0), b(3) }

	RefHolder ::= SEQUENCE {
		ref	RangedBits OPTIONAL,
		caps	CapsBits OPTIONAL,
		flag	BOOLEAN
	}

END

BitsB DEFINITIONS AUTOMATIC TAGS ::=
BEGIN
	IMPORTS RangedBits, CapsBits FROM BitsA;

	-- owns its own BIT STRING member (and thus its own BitString)
	OwnBits ::= SEQUENCE {
		b	BIT STRING (SIZE(4)),
		flag	BOOLEAN
	}

	-- OPTIONAL references to BIT STRING types of another module
	XRefHolder ::= SEQUENCE {
		ref	RangedBits OPTIONAL,
		caps	CapsBits OPTIONAL,
		flag	BOOLEAN
	}

END

BitsC DEFINITIONS AUTOMATIC TAGS ::=
BEGIN
	IMPORTS RangedBits FROM BitsA;

	-- no BIT STRING of its own: the member types come from BitsA
	ImpHolder ::= SEQUENCE {
		req	RangedBits,
		opt	RangedBits OPTIONAL,
		flag	BOOLEAN
	}

END

EBS DEFINITIONS AUTOMATIC TAGS ::= BEGIN

-- A zero-length BIT STRING is a valid value: as an OPTIONAL and a plain
-- SEQUENCE member (next to OCTET STRINGs), as a CHOICE alternative and as a
-- SEQUENCE OF element.
EbT ::= SEQUENCE { o BIT STRING OPTIONAL, p BIT STRING, q OCTET STRING, r OCTET STRING OPTIONAL }
EbC ::= CHOICE { a BIT STRING, b INTEGER (0..3) }
EbL ::= SEQUENCE OF BIT STRING

END
