Shadow DEFINITIONS AUTOMATIC TAGS ::=
BEGIN

-- An inline SEQUENCE (or CHOICE) is its own Go struct, so its field names
-- never clash with the fields of the enclosing struct, whatever the order.

	ShL ::= INTEGER (0..7)

	-- inner x, outer x
	ShSeq ::= SEQUENCE {
		a	SEQUENCE { x BOOLEAN, y INTEGER (0..3) },
		x	BOOLEAN
	}

	-- outer field first, inner after
	ShSeqRev ::= SEQUENCE {
		x	BOOLEAN,
		a	SEQUENCE { x BOOLEAN, y INTEGER (0..3) }
	}

	ShChoice ::= CHOICE {
		a	SEQUENCE { x BOOLEAN, l INTEGER (0..7) },
		l	INTEGER (0..7)
	}

	ShDeep ::= SEQUENCE {
		p	CHOICE {
			a	SEQUENCE { x BOOLEAN, l ShL },
			l	ShL
		}
	}

	-- sibling inline SEQUENCEs with one field name; a field named like its member
	ShSib ::= SEQUENCE {
		a	SEQUENCE { l BOOLEAN },
		b	SEQUENCE { l BOOLEAN },
		c	SEQUENCE { c BOOLEAN }
	}

END
