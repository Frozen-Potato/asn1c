XbsA DEFINITIONS AUTOMATIC TAGS ::= BEGIN

-- BIT STRING shapes imported by a module that also declares its own BIT
-- STRING (so each package has its own BitString type): a plain member, a
-- DEFAULT member, an inline SEQUENCE OF BIT STRING and a named one.
XbPlain ::= SEQUENCE { bm BIT STRING { c1(0), c2(1) } (SIZE(8)), n INTEGER (0..7) }
XbDef ::= SEQUENCE { bm BIT STRING (SIZE(4)) DEFAULT '1010'B, n INTEGER (0..7) }
XbInl ::= SEQUENCE { l SEQUENCE OF BIT STRING (SIZE(4)) }
XbList ::= SEQUENCE OF BIT STRING (SIZE(4))

END

XbsB DEFINITIONS AUTOMATIC TAGS ::= BEGIN

IMPORTS XbPlain, XbDef, XbInl, XbList FROM XbsA;

XbMsg ::= SEQUENCE {
	p XbPlain,
	d XbDef,
	i XbInl,
	l XbList,
	own BIT STRING (SIZE(4))
}

END
