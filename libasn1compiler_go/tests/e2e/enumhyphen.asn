EnumHyphen DEFINITIONS AUTOMATIC TAGS ::= BEGIN

-- Enumerators and named bits that differ only by a hyphen.

Drift ::= ENUMERATED { d1, d-1, d2, d-2, ... }

B ::= BIT STRING { b1(0), b-1(1) }

T ::= SEQUENCE {
	e	ENUMERATED { a1, a-1 },
	d	Drift,
	b	B
}

END
