XmsA DEFINITIONS AUTOMATIC TAGS ::= BEGIN

-- A named SEQUENCE OF imported by other modules.
XsItem ::= SEQUENCE { a INTEGER (0..7) }
XsList ::= SEQUENCE (SIZE(1..4)) OF XsItem

END

XmsB DEFINITIONS AUTOMATIC TAGS ::= BEGIN

IMPORTS XsList FROM XmsA;

XsMsgOpt ::= SEQUENCE { i INTEGER (0..3), l XsList OPTIONAL }
XsMsgReq ::= SEQUENCE { l XsList, i INTEGER (0..3) }
-- imported by XmsC, which also imports XsList itself
XsSide ::= SEQUENCE { i INTEGER (0..3), l XsList OPTIONAL }

END

XmsC DEFINITIONS AUTOMATIC TAGS ::= BEGIN

-- reaches the list both directly and through XmsB's type
IMPORTS XsSide FROM XmsB
        XsList FROM XmsA;

XsTop ::= SEQUENCE { o XsSide, l XsList }

END
