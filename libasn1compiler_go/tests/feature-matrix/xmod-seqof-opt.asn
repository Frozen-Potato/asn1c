ModA DEFINITIONS AUTOMATIC TAGS ::= BEGIN
It ::= SEQUENCE { n INTEGER (0..7) }
SP ::= SEQUENCE { l SEQUENCE (SIZE(1..4)) OF It OPTIONAL }
END
ModB DEFINITIONS AUTOMATIC TAGS ::= BEGIN
IMPORTS SP FROM ModA;
Msg ::= SEQUENCE { sp SP }
END
