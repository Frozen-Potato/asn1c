ModA DEFINITIONS AUTOMATIC TAGS ::= BEGIN
Item ::= SEQUENCE { a INTEGER (0..7) }
ItemList ::= SEQUENCE (SIZE(1..4)) OF Item
END

ModB DEFINITIONS AUTOMATIC TAGS ::= BEGIN
IMPORTS ItemList FROM ModA;
Msg ::= SEQUENCE { l ItemList OPTIONAL }
Req ::= SEQUENCE { l ItemList }
END
