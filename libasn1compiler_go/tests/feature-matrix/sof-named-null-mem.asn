Probe DEFINITIONS AUTOMATIC TAGS ::= BEGIN

N ::= NULL
T ::= SEQUENCE {
    a SEQUENCE (SIZE(0..3)) OF N,
    b SEQUENCE (SIZE(0..3)) OF N OPTIONAL,
    c BOOLEAN
}
U ::= CHOICE { a SEQUENCE (SIZE(0..3)) OF N, b BOOLEAN }

END
