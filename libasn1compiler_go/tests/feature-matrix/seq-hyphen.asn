Probe DEFINITIONS AUTOMATIC TAGS ::= BEGIN

-- SEQUENCE fields that differ only by a hyphen before a digit; both with an
-- inline SEQUENCE, one with a DEFAULT.
T ::= SEQUENCE {
    a1  SEQUENCE { x INTEGER (0..9) },
    a-1 SEQUENCE { y BOOLEAN },
    b1  BOOLEAN DEFAULT TRUE,
    b-1 INTEGER (0..9) DEFAULT 4
}

END
