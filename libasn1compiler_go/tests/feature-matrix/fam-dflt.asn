Probe DEFINITIONS AUTOMATIC TAGS ::= BEGIN

-- dflt-enum-ok
DfltEnumOk ::= SEQUENCE { a ENUMERATED { x, y } DEFAULT y, b BOOLEAN }

-- dflt-ia5
DfltIa5 ::= SEQUENCE { a IA5String DEFAULT "hi", b BOOLEAN }

-- dflt-bmp
DfltBmp ::= SEQUENCE { a BMPString DEFAULT "hi", b BOOLEAN }

-- dflt-universal
DfltUniversal ::= SEQUENCE { a UniversalString DEFAULT "hi", b BOOLEAN }

-- dflt-utf8
DfltUtf8 ::= SEQUENCE { a UTF8String DEFAULT "é€", b BOOLEAN }

-- dflt-utctime
DfltUtctime ::= SEQUENCE { a UTCTime DEFAULT "250102030405Z", b BOOLEAN }

-- dflt-gentime
DfltGentime ::= SEQUENCE { a GeneralizedTime DEFAULT "20250102030405Z", b BOOLEAN }

-- dflt-other-str
DfltOtherStr ::= SEQUENCE {
    gen GeneralString DEFAULT "g", gra GraphicString DEFAULT "g",
    tel TeletexString DEFAULT "g", t61 T61String DEFAULT "g",
    vid VideotexString DEFAULT "g", od ObjectDescriptor DEFAULT "g", b BOOLEAN }

-- dflt-null
DfltNull ::= SEQUENCE { a NULL DEFAULT NULL, b BOOLEAN }

-- dflt-real
DfltReal ::= SEQUENCE { a REAL DEFAULT 1.5, b BOOLEAN }

-- dflt-real-forms
DfltRealForms ::= SEQUENCE {
    z REAL DEFAULT 0, m REAL DEFAULT -2.25, i REAL DEFAULT 2, e REAL DEFAULT 1e3,
    p REAL DEFAULT PLUS-INFINITY, q REAL DEFAULT MINUS-INFINITY,
    n REAL DEFAULT NOT-A-NUMBER, nz REAL DEFAULT -0.0, b BOOLEAN }

-- dflt-namedbit
DfltNamedBit ::= SEQUENCE { a BIT STRING { p(0), q(1) } DEFAULT { p }, b BOOLEAN }

-- dflt-namedbit-forms
NbPerms ::= BIT STRING { read(0), write(1) } (SIZE (8))
DfltNamedBitForms ::= SEQUENCE {
    e BIT STRING { p(0), q(1) } DEFAULT { },
    f BIT STRING { p(0), q(1) } DEFAULT { p, q },
    g NbPerms DEFAULT { read },
    h BIT STRING { p(0), q(1) } DEFAULT '01'B, b BOOLEAN }

-- dflt-oid
DfltOid ::= SEQUENCE { a OBJECT IDENTIFIER DEFAULT { 1 3 6 }, b BOOLEAN }

-- dflt-oid-forms
DfltOidForms ::= SEQUENCE {
    a OBJECT IDENTIFIER DEFAULT { iso(1) org(3) 6 1 },
    c OBJECT IDENTIFIER DEFAULT { joint-iso-itu-t 5 },
    d OBJECT IDENTIFIER DEFAULT { 2 999 4294967295 }, b BOOLEAN }

-- dflt-roid
DfltRoid ::= SEQUENCE { a RELATIVE-OID DEFAULT { 1 2 }, b BOOLEAN }

-- dflt-oid-ref
dflt-oid-ref-base OBJECT IDENTIFIER ::= { 1 3 6 1 }
dflt-oid-ref-rel RELATIVE-OID ::= { 8 9 }
DfltOidRef ::= SEQUENCE {
    a OBJECT IDENTIFIER DEFAULT dflt-oid-ref-base,
    c OBJECT IDENTIFIER DEFAULT { dflt-oid-ref-base 5 },
    d OBJECT IDENTIFIER DEFAULT { dflt-oid-ref-base dflt-oid-ref-rel },
    r RELATIVE-OID DEFAULT { dflt-oid-ref-rel 1 }, b BOOLEAN }

END
