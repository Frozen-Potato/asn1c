Probe DEFINITIONS AUTOMATIC TAGS ::= BEGIN

-- CHOICE alternatives that differ only by a hyphen before a digit (a NULL
-- one, and two with an inline SEQUENCE).
T ::= CHOICE {
    a1  BOOLEAN,
    a-1 NULL,
    c1  SEQUENCE { x INTEGER (0..9) },
    c-1 SEQUENCE { y BOOLEAN }
}

END
