ModA DEFINITIONS AUTOMATIC TAGS ::= BEGIN
Rnti ::= BIT STRING (SIZE(16))
SP ::= SEQUENCE { r Rnti OPTIONAL }
END
ModB DEFINITIONS AUTOMATIC TAGS ::= BEGIN
IMPORTS SP FROM ModA;
Msg ::= SEQUENCE { sp SP }
END
