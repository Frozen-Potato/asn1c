Probe DEFINITIONS AUTOMATIC TAGS ::= BEGIN

-- CHOICE alternatives named after C reserved words: the union member is
-- upcased (`Explicit`), the _PR constant keeps the lower case.
C ::= CHOICE { explicit BOOLEAN, int INTEGER (0..3), struct CHOICE { p BOOLEAN, q NULL }, x NULL }

END
