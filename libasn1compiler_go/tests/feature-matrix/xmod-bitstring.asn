ModA DEFINITIONS AUTOMATIC TAGS ::= BEGIN
SP ::= SEQUENCE { bm BIT STRING { c1(0), c2(1) } (SIZE(8)), n INTEGER (0..7) }
END
ModB DEFINITIONS AUTOMATIC TAGS ::= BEGIN
IMPORTS SP FROM ModA;
Msg ::= SEQUENCE { sp SP, own BIT STRING (SIZE(4)) }
END
