Probe DEFINITIONS AUTOMATIC TAGS ::= BEGIN

-- An alias of a CHOICE with an inline SEQUENCE alternative: C has only
-- `typedef Orig_t Alias_t;`, so the converters use Orig_PR and struct Orig__t2.
Orig ::= CHOICE {
    t1 INTEGER (0..31),
    t2 SEQUENCE { p1 INTEGER (0..23), p2 INTEGER (1..3) OPTIONAL }
}
Alias ::= Orig
L ::= SEQUENCE (SIZE(1..4)) OF Alias

END
